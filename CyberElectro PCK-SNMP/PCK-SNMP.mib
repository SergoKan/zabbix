PCK-SNMP-MIB DEFINITIONS ::= BEGIN

IMPORTS 
        TEXTUAL-CONVENTION FROM SNMPv2-TC
        MODULE-IDENTITY, OBJECT-TYPE, OBJECT-IDENTITY, NOTIFICATION-TYPE, TimeTicks, IpAddress, enterprises FROM SNMPv2-SMI
        DisplayString, TimeStamp, TimeInterval, TestAndIncr, AutonomousType FROM SNMPv2-TC
        mib-2 FROM RFC1213-MIB
        Counter FROM RFC1155-SMI;

pck MODULE-IDENTITY
    LAST-UPDATED    "2001070000Z"
    ORGANIZATION    "SPETSPROMDIZAIN LLC"
    CONTACT-INFO    "Frolov Dmitry
                     e-mail: info@spd.net.ru"
    DESCRIPTION     "SPETSPROMDIZAIN MIB OID defines"
    REVISION        "2001070000Z"
    DESCRIPTION     "v.1"
    ::= { enterprises 53722 }

PositiveInteger ::= TEXTUAL-CONVENTION
    DISPLAY-HINT "d"
    STATUS       current
    DESCRIPTION  "This data type is a non-zero and non-negative value"
    SYNTAX       INTEGER (1..2147483647)
    
pcksnmp            OBJECT IDENTIFIER ::= { pck 117 }
params             OBJECT IDENTIFIER ::= { pcksnmp 0 }
traps              OBJECT IDENTIFIER ::= { pcksnmp 1 }
                   
cm                 OBJECT IDENTIFIER ::= { enterprises 935 }
products           OBJECT IDENTIFIER ::= { cm 1 }
hardware           OBJECT IDENTIFIER ::= { products 1 }
ups                OBJECT IDENTIFIER ::= { hardware 1 }
upsBatteryp        OBJECT IDENTIFIER ::= { ups 2 }
upsOutputp         OBJECT IDENTIFIER ::= { ups 4 }
upsConfigp         OBJECT IDENTIFIER ::= { ups 5 }
upsBaseBattery     OBJECT IDENTIFIER ::= { upsBatteryp 1 }
upsSmartBattery    OBJECT IDENTIFIER ::= { upsBatteryp 2 }
upsBaseOutput      OBJECT IDENTIFIER ::= { upsOutputp 1 }
upsSmartConfig     OBJECT IDENTIFIER ::= { upsConfigp 2 }
                   
ups-mib            OBJECT IDENTIFIER ::= { mib-2 33 }
upsObjects         OBJECT IDENTIFIER ::= { ups-mib 1 }
upsIdent           OBJECT IDENTIFIER ::= { upsObjects 1 }
upsBattery         OBJECT IDENTIFIER ::= { upsObjects 2 }
upsInput           OBJECT IDENTIFIER ::= { upsObjects 3 }
upsOutput          OBJECT IDENTIFIER ::= { upsObjects 4 }
upsBypass          OBJECT IDENTIFIER ::= { upsObjects 5 }
upsAlarm           OBJECT IDENTIFIER ::= { upsObjects 6 }
upsTest            OBJECT IDENTIFIER ::= { upsObjects 7 }
upsControl         OBJECT IDENTIFIER ::= { upsObjects 8 }
upsConfig          OBJECT IDENTIFIER ::= { upsObjects 9 }
upsWellKnownAlarms OBJECT IDENTIFIER ::= { upsAlarm 3 }

------------------------------
-- Client Mate
------------------------------

upsBaseBatteryStatus OBJECT-TYPE
    SYNTAX      INTEGER { unknown(1), batteryNormal(2), batteryLow(3) }
    MAX-ACCESS  read-only
    STATUS      current
    DESCRIPTION "The status of the UPS batteries.  A batteryLow(3) value indicates the UPS will be unable to sustain the current load, and its services will be lost if power is not restored.
                 The amount of run time in reserve at the time of low battery can be configured by the upsSmartConfigLowBatteryRunTime"
    ::= { upsBaseBattery 1 }

upsBaseBatteryTimeOnBattery OBJECT-TYPE
    SYNTAX      INTEGER
    MAX-ACCESS  read-only
    STATUS      current
    DESCRIPTION "The elapsed time in seconds since the UPS has switched to battery power"
    ::= { upsBaseBattery 2 }

upsSmartBatteryCapacity OBJECT-TYPE
    SYNTAX      INTEGER
    MAX-ACCESS  read-only
    STATUS      current
    DESCRIPTION "The remaining battery capacity expressed in percent of full capacity"
    ::= { upsSmartBattery 1 }

upsSmartBatteryRunTimeRemaining OBJECT-TYPE
    SYNTAX      INTEGER
    MAX-ACCESS  read-only
    STATUS      current
    DESCRIPTION "The UPS battery run time remaining before battery exhaustion, in seconds"
    ::= { upsSmartBattery 4 }

upsBaseOutputStatus OBJECT-TYPE
    SYNTAX      INTEGER { unknown(1), onLine(2), onBattery(3), onBoost(4), sleeping(5), onBypass(6), rebooting(7), standBy(8), onBuck(9) }
    MAX-ACCESS  read-only
    STATUS      current
    DESCRIPTION "The current state of the UPS.  If the UPS is unable to determine the state of the UPS this variable is set to unknown(1)"
    ::= { upsBaseOutput 1 }

upsSmartConfigAlarmTimer OBJECT-TYPE
    SYNTAX      INTEGER
    MAX-ACCESS  read-write
    STATUS      current
    DESCRIPTION "The time in seconds after initial line failure at which the UPS begins emitting audible alarms (beeping).  This timer is observerd only if the value of extControlAlarm is timed(2).
                 Allowed values are 0 or 30 seconds.
                 If a value other than a supported value is provided in a set request, the UPS interprets it as a the next lower acceptable value.  If the provided value is lower than the lowest
                 acceptable value, the lowest acceptable value is used"
    ::= { upsSmartConfig 5 }

------------------------------
-- NUT
------------------------------

-- upsIdent

upsIdentManufacturer OBJECT-TYPE
    SYNTAX      DisplayString (SIZE (0..24))
    MAX-ACCESS  read-only
    STATUS      current
    DESCRIPTION "The name of the UPS manufacturer"
    ::= { upsIdent 1 }

upsIdentModel OBJECT-TYPE
    SYNTAX      DisplayString (SIZE (0..24))
    MAX-ACCESS  read-only
    STATUS      current
    DESCRIPTION "The UPS Model designation"
    ::= { upsIdent 2 }

upsIdentUPSSoftwareVersion OBJECT-TYPE
    SYNTAX      DisplayString (SIZE (0..24))
    MAX-ACCESS  read-only
    STATUS      current
    DESCRIPTION "The UPS firmware/software version(s). This variable may or may not have the same value as upsIdentAgentSoftwareVersion in some implementations"
    ::= { upsIdent 3 }

upsIdentAgentSoftwareVersion OBJECT-TYPE
    SYNTAX     DisplayString (SIZE (0..24))
    MAX-ACCESS read-only
    STATUS     current
    DESCRIPTION "The UPS agent software version. This variable may or may not have the same value as upsIdentUPSSoftwareVersion in some implementations"
    ::= { upsIdent 4 }

upsIdentName OBJECT-TYPE
    SYNTAX      DisplayString (SIZE(0..24))
    MAX-ACCESS  read-write
    STATUS      current
    DESCRIPTION "A string identifying the UPS. This object should be set by the administrator"
    ::= { upsIdent 5 }

upsIdentAttachedDevices OBJECT-TYPE
    SYNTAX      DisplayString (SIZE(0..24))
    MAX-ACCESS  read-write
    STATUS      current
    DESCRIPTION "A string identifying the devices attached to the output(s) of the UPS. This object should be set by the administrator"
    ::= { upsIdent 6 }

-- upsBattery

upsBatteryStatus OBJECT-TYPE
    SYNTAX      INTEGER { unknown(1), batteryNormal(2), batteryLow(3), batteryDepleted(4) }
    MAX-ACCESS  read-only
    STATUS      current
    DESCRIPTION "The indication of the capacity remaining in the UPS system's batteries. A value of batteryNormal indicates that the remaining run-time is greater than upsConfigLowBattTime.
                A value of batteryLow indicates that the remaining battery run-time is less than or equal to upsConfigLowBattTime.  A value of batteryDepleted indicates that the UPS will be unable
                to sustain the present load when and if the utility power is lost (including the possibility that the utility power is currently absent and the UPS is unable to sustain the output)"
    ::= { upsBattery 1 }

upsSecondsOnBattery OBJECT-TYPE
    SYNTAX      INTEGER
    MAX-ACCESS  read-only
    STATUS      current
    DESCRIPTION "If the unit is on battery power, the elapsed time since the UPS last switched to battery power, or the time since the network management subsystem was last restarted,
                whichever is less. Zero shall be returned if the unit is not on battery power"
    ::= { upsBattery 2 }

upsEstimatedMinutesRemaining OBJECT-TYPE
    SYNTAX      INTEGER
    MAX-ACCESS  read-only
    STATUS      current
    DESCRIPTION "An estimate of the time to battery charge depletion under the present load conditions if the utility power is off and remains off, or if it were to be lost and remain off"
    ::= { upsBattery 3 }

upsEstimatedChargeRemaining OBJECT-TYPE
    SYNTAX      INTEGER (0..100)
    MAX-ACCESS  read-only
    STATUS      current
    DESCRIPTION "An estimate of the battery charge remaining expressed as a percent of full charge"
    ::= { upsBattery 4 }

upsBatteryVoltage OBJECT-TYPE
    SYNTAX      INTEGER
    MAX-ACCESS  read-only
    STATUS      current
    DESCRIPTION "The magnitude of the present battery voltage (0.1V)"
    ::= { upsBattery 5 }

upsBatteryCurrent OBJECT-TYPE
    SYNTAX      INTEGER
    MAX-ACCESS  read-only
    STATUS      current
    DESCRIPTION "The present battery current (0.1A)"
    ::= { upsBattery 6 }

upsBatteryTemperature OBJECT-TYPE
    SYNTAX      INTEGER
    MAX-ACCESS  read-only
    STATUS      current
    DESCRIPTION "The ambient temperature at or near the UPS Battery casing (C)"
    ::= { upsBattery 7 }

-- upsInput

upsInputLineBads OBJECT-TYPE
    SYNTAX      INTEGER
    MAX-ACCESS  read-only
    STATUS      current
    DESCRIPTION "A count of the number of times the input entered an out-of-tolerance condition as defined by the manufacturer.  This count is incremented by one each time the input transitions
                from zero out-of-tolerance lines to one or more input lines out-of-tolerance"
    ::= { upsInput 1 }

upsInputNumLines OBJECT-TYPE
    SYNTAX      INTEGER
    MAX-ACCESS  read-only
    STATUS      current
    DESCRIPTION "The number of input lines utilized in this device. This variable indicates the number of rows in the input table"
    ::= { upsInput 2 }

upsInputTable OBJECT-TYPE
    SYNTAX      SEQUENCE OF UpsInputEntry
    MAX-ACCESS  not-accessible
    STATUS      current
    DESCRIPTION "A list of input table entries. The number of entries is given by the value of upsInputNumLines"
    ::= { upsInput 3 }

upsInputEntry OBJECT-TYPE
    SYNTAX      UpsInputEntry
    MAX-ACCESS  not-accessible
    STATUS      current
    DESCRIPTION "An entry containing information applicable to a particular input line"
    INDEX { upsInputLineIndex }
    ::= { upsInputTable 1 }

UpsInputEntry ::= SEQUENCE {
    upsInputLineIndex PositiveInteger,
    upsInputFrequency INTEGER,
    upsInputVoltage   INTEGER,
    upsInputCurrent   INTEGER,
    upsInputTruePower INTEGER
}

upsInputLineIndex OBJECT-TYPE
    SYNTAX      PositiveInteger
    MAX-ACCESS  not-accessible
    STATUS      current
    DESCRIPTION "The input line identifier"
    ::= { upsInputEntry 1 }

upsInputFrequency OBJECT-TYPE
    SYNTAX      INTEGER
    MAX-ACCESS  read-only
    STATUS      current
    DESCRIPTION "The present input frequency (0.1 Hz)"
    ::= { upsInputEntry 2 }

upsInputVoltage OBJECT-TYPE
    SYNTAX      INTEGER
    MAX-ACCESS  read-only
    STATUS      current
    DESCRIPTION "The magnitude of the present input voltage (V)"
    ::= { upsInputEntry 3 }

upsInputCurrent OBJECT-TYPE
    SYNTAX      INTEGER
    MAX-ACCESS  read-only
    STATUS      current
    DESCRIPTION "The magnitude of the present input current (0.1A)"
    ::= { upsInputEntry 4 }

upsInputTruePower OBJECT-TYPE
    SYNTAX      INTEGER
    MAX-ACCESS  read-only
    STATUS      current
    DESCRIPTION "The magnitude of the present input true power (W)"
    ::= { upsInputEntry 5 }

-- upsOutput

upsOutputSource OBJECT-TYPE
    SYNTAX      INTEGER { other(1), none(2), normal(3), bypass(4), battery(5), booster(6), reducer(7) }
    MAX-ACCESS  read-only
    STATUS      current
    DESCRIPTION "The present source of output power. The enumeration none(2) indicates that there is no source of output power (and therefore no output power),
                for example, the system has openedthe output breaker"
    ::= { upsOutput 1 }

upsOutputFrequency OBJECT-TYPE
    SYNTAX      INTEGER
    MAX-ACCESS  read-only
    STATUS      current
    DESCRIPTION "The present output frequency (0.1 Hz)"
    ::= { upsOutput 2 }

upsOutputNumLines OBJECT-TYPE
    SYNTAX      INTEGER
    MAX-ACCESS  read-only
    STATUS      current
    DESCRIPTION "The number of output lines utilized in this device. This variable indicates the number of rows in the output table"
    ::= { upsOutput 3 }

upsOutputTable OBJECT-TYPE
    SYNTAX      SEQUENCE OF UpsOutputEntry
    MAX-ACCESS  not-accessible
    STATUS      current
    DESCRIPTION "A list of output table entries. The number of entries is given by the value of upsOutputNumLines"
    ::= { upsOutput 4 }

upsOutputEntry OBJECT-TYPE
    SYNTAX      UpsOutputEntry
    MAX-ACCESS  not-accessible
    STATUS      current
    DESCRIPTION "An entry containing information applicable to a particular output line"
    INDEX { upsOutputLineIndex }
    ::= { upsOutputTable 1 }

UpsOutputEntry ::= SEQUENCE {
    upsOutputLineIndex   PositiveInteger,
    upsOutputVoltage     INTEGER,
    upsOutputCurrent     INTEGER,
    upsOutputPower       INTEGER,
    upsOutputPercentLoad INTEGER
}

upsOutputLineIndex OBJECT-TYPE
    SYNTAX      PositiveInteger
    MAX-ACCESS  not-accessible
    STATUS      current
    DESCRIPTION "The output line identifier"
    ::= { upsOutputEntry 1 }

upsOutputVoltage OBJECT-TYPE
    SYNTAX      INTEGER
    MAX-ACCESS  read-only
    STATUS      current
    DESCRIPTION "The present output voltage (V)"
    ::= { upsOutputEntry 2 }

upsOutputCurrent OBJECT-TYPE
    SYNTAX      INTEGER
    MAX-ACCESS  read-only
    STATUS      current
    DESCRIPTION "The present output current (0.1A)"
    ::= { upsOutputEntry 3 }

upsOutputPower OBJECT-TYPE
    SYNTAX      INTEGER
    MAX-ACCESS  read-only
    STATUS      current
    DESCRIPTION "The present output true power (W)"
    ::= { upsOutputEntry 4 }

upsOutputPercentLoad OBJECT-TYPE
    SYNTAX      INTEGER (0..200)
    MAX-ACCESS  read-only
    STATUS      current
    DESCRIPTION "The percentage of the UPS power capacity presently being used on this output line, i.e., the greater of the percent load of true power capacity and the percent load of VA"
    ::= { upsOutputEntry 5 }

-- upsBypass

upsBypassFrequency OBJECT-TYPE
    SYNTAX      INTEGER
    MAX-ACCESS  read-only
    STATUS      current
    DESCRIPTION "The present bypass frequency (0.1 Hz)"
    ::= { upsBypass 1 }

upsBypassNumLines OBJECT-TYPE
    SYNTAX      INTEGER
    MAX-ACCESS  read-only
    STATUS      current
    DESCRIPTION "The number of bypass lines utilized in this device. This entry indicates the number of rows in the bypass table"
    ::= { upsBypass 2 }

upsBypassTable OBJECT-TYPE
    SYNTAX      SEQUENCE OF UpsBypassEntry
    MAX-ACCESS  not-accessible
    STATUS      current
    DESCRIPTION "A list of bypass table entries. The number of entries is given by the value of upsBypassNumLines"
    ::= { upsBypass 3 }

upsBypassEntry OBJECT-TYPE
    SYNTAX     UpsBypassEntry
    MAX-ACCESS  not-accessible
    STATUS      current
    DESCRIPTION "An entry containing information applicable to a particular bypass input"
    INDEX { upsBypassLineIndex }
    ::= { upsBypassTable 1 }

UpsBypassEntry ::= SEQUENCE {
    upsBypassLineIndex  PositiveInteger,
    upsBypassVoltage    INTEGER,
    upsBypassCurrent    INTEGER,
    upsBypassPower      INTEGER
}

upsBypassLineIndex OBJECT-TYPE
    SYNTAX      PositiveInteger
    MAX-ACCESS  not-accessible
    STATUS      current
    DESCRIPTION "The bypass line identifier"
    ::= { upsBypassEntry 1 }

upsBypassVoltage OBJECT-TYPE
    SYNTAX      INTEGER
    MAX-ACCESS  read-only
    STATUS      current
    DESCRIPTION "The present bypass voltage (V)"
    ::= { upsBypassEntry 2 }

upsBypassCurrent OBJECT-TYPE
    SYNTAX      INTEGER
    MAX-ACCESS  read-only
    STATUS      current
    DESCRIPTION "The present bypass current (0.1A)"
    ::= { upsBypassEntry 3 }

upsBypassPower OBJECT-TYPE
    SYNTAX      INTEGER
    MAX-ACCESS  read-only
    STATUS      current
    DESCRIPTION "The present true power conveyed by the bypass (W)"
    ::= { upsBypassEntry 4 }

-- upsAlarm

upsAlarmsPresent OBJECT-TYPE
    SYNTAX      INTEGER
    MAX-ACCESS  read-only
    STATUS      current
    DESCRIPTION "The present number of active alarm conditions"
    ::= { upsAlarm 1 }

upsAlarmTable OBJECT-TYPE
    SYNTAX      SEQUENCE OF UpsAlarmEntry
    MAX-ACCESS  not-accessible
    STATUS      current
    DESCRIPTION "A list of alarm table entries. The table contains zero, one, or many rows at any moment, depending upon the number of alarm conditions in effect. The table is initially
                empty at agent startup. The agent creates a row in the table each time a condition is detected and deletes that row when that condition no longer pertains.
                The agent creates the first row with upsAlarmId equal to 1, and increments the value of upsAlarmId each time a new row is created, wrapping to the first free value greater
                than or equal to 1 when the maximum value of upsAlarmId would otherwise be exceeded. Consequently, after multiple operations, the table may become sparse, e.g., containing
                entries for rows 95, 100, 101, and 203 and the entries should not be assumed to be in chronological order because upsAlarmId might have wrapped.

                Alarms are named by an AutonomousType (OBJECT IDENTIFIER), upsAlarmDescr, to allow a single table to reflect well known alarms plus alarms defined by a particular implementation,
                i.e., as documented in the private enterprise MIB definition for the device. No two rows will have the same value of upsAlarmDescr, since alarms define conditions. In order to meet this
                requirement, care should be taken in the definition of alarm conditions to insure that a system cannot enter the same condition multiple times simultaneously.

                The number of rows in the table at any given time is reflected by the value of upsAlarmsPresent"
    ::= { upsAlarm 2 }

   upsAlarmEntry OBJECT-TYPE
       SYNTAX      UpsAlarmEntry
       MAX-ACCESS  not-accessible
       STATUS      current
       DESCRIPTION "An entry containing information applicable to a particular alarm"
       INDEX { upsAlarmId }
       ::= { upsAlarmTable 1 }

   UpsAlarmEntry ::= SEQUENCE {
       upsAlarmId    PositiveInteger,
       upsAlarmDescr AutonomousType,
       upsAlarmTime  TimeStamp
   }

   upsAlarmId OBJECT-TYPE
       SYNTAX      PositiveInteger
       MAX-ACCESS  not-accessible
       STATUS      current
       DESCRIPTION "A unique identifier for an alarm condition. This value must remain constant"
       ::= { upsAlarmEntry 1 }

   upsAlarmDescr OBJECT-TYPE
       SYNTAX      AutonomousType
       MAX-ACCESS  read-only
       STATUS      current
       DESCRIPTION "A reference to an alarm description object. The object referenced should not be accessible, but rather be used to provide a unique description of the alarm condition"
       ::= { upsAlarmEntry 2 }

   upsAlarmTime OBJECT-TYPE
       SYNTAX      TimeStamp
       MAX-ACCESS  read-only
       STATUS      current
       DESCRIPTION "The value of sysUpTime when the alarm condition was detected.  If the alarm condition was detected at the time of agent startup and presumably existed before agent startup,
                   the value of upsAlarmTime shall equal 0"
       ::= { upsAlarmEntry 3 }

-- upsWellKnownAlarms

upsAlarmBatteryBad OBJECT-IDENTITY
    STATUS      current
    DESCRIPTION "One or more batteries have been determined to require replacement"
    ::= { upsWellKnownAlarms 1 }

upsAlarmOnBattery OBJECT-IDENTITY
    STATUS      current
    DESCRIPTION "The UPS is drawing power from the batteries"
    ::= { upsWellKnownAlarms 2 }

upsAlarmLowBattery OBJECT-IDENTITY
    STATUS      current
    DESCRIPTION "The remaining battery run-time is less than or equal to upsConfigLowBattTime"
    ::= { upsWellKnownAlarms 3 }

upsAlarmTempBad OBJECT-IDENTITY
    STATUS      current
    DESCRIPTION "A temperature is out of tolerance"
    ::= { upsWellKnownAlarms 5 }

upsAlarmOutputOverload OBJECT-IDENTITY
    STATUS      current
    DESCRIPTION "The output load exceeds the UPS output capacity"
    ::= { upsWellKnownAlarms 8 }

-- upsTest

upsTestId OBJECT-TYPE
    SYNTAX      OBJECT IDENTIFIER
    MAX-ACCESS  read-only
    STATUS      current
    DESCRIPTION "The test is named by an OBJECT IDENTIFIER which allows a standard mechanism for the initiation of tests, including the well known tests identified in
                this document as well as those introduced by a particular implementation, i.e., as documented in the private enterprise MIB definition for the device.
                
                Setting this variable initiates the named test. Sets to this variable require the presence of upsTestSpinLock in the same SNMP message.
                
                The set request will be rejected with an appropriate error message if the requested test cannot be performed, including attempts to start a test when
                another test is already in progress.  The status of the current or last test is maintained in upsTestResultsSummary. Tests in progress may be aborted by
                setting the upsTestId variable to upsTestAbortTestInProgress.
                
                Read operations return the value of the name of the test in progress if a test is in progress or the name of the last test performed if no test is in progress,
                unless no test has been run, in which case the well known value upsTestNoTestsInitiated is returned"
    ::= { upsTest 1 }

upsTestSpinLock OBJECT-TYPE
    SYNTAX      TestAndIncr
    MAX-ACCESS  read-only
    STATUS      current
    DESCRIPTION "A spin lock on the test subsystem. The spinlock is used as follows"
    ::= { upsTest 2 }

upsTestResultsSummary OBJECT-TYPE
    SYNTAX      INTEGER { donePass(1), doneWarning(2), doneError(3), aborted(4), inProgress(5), noTestsInitiated(6) }
    MAX-ACCESS  read-only
    STATUS      current
    DESCRIPTION "The results of the current or last UPS diagnostics test performed.  The values for donePass(1), doneWarning(2), and doneError(3) indicate that the
                test completed either successfully, with a warning, or with an error, respectively.  The value aborted(4) is returned for tests which are aborted by setting the
                value of upsTestId to upsTestAbortTestInProgress. Tests which have not yet concluded are indicated by inProgress(5).  The value noTestsInitiated(6) indicates
                that no previous test results are available, such as is the case when no tests have been run since the last reinitialization of the network management
                subsystem and the system has no provision for non-volatile storage of test results"
    ::= { upsTest 3 }

upsTestResultsDetail OBJECT-TYPE
    SYNTAX      DisplayString (SIZE (0..255))
    MAX-ACCESS  read-only
    STATUS      current
    DESCRIPTION "Additional information about upsTestResultsSummary. If no additional information available, a zero length string is returned"
    ::= { upsTest 4 }

upsTestStartTime OBJECT-TYPE
    SYNTAX      TimeStamp
    MAX-ACCESS  read-only
    STATUS      current
    DESCRIPTION "The value of sysUpTime at the time the test in progress was initiated, or, if no test is in progress, the time the previous test was initiated.
                If the value of upsTestResultsSummary is noTestsInitiated(6), upsTestStartTime has the value 0"
    ::= { upsTest 5 }

upsTestElapsedTime OBJECT-TYPE
    SYNTAX      INTEGER
    MAX-ACCESS  read-only
    STATUS      current
    DESCRIPTION "The amount of time, in TimeTicks, since the test in progress was initiated, or, if no test is in progress, the previous test took to complete.
                If the value of upsTestResultsSummary is noTestsInitiated(6), upsTestElapsedTime has the value 0"
    ::= { upsTest 6 }

-- upsControl

upsShutdownType OBJECT-TYPE
    SYNTAX      INTEGER { output(1), system(2) }
    MAX-ACCESS  read-write
    STATUS      current
    DESCRIPTION "This object determines the nature of the action to be taken at the time when the countdown of the upsShutdownAfterDelay and upsRebootWithDuration
                 objects reaches zero.

                 Setting this object to output(1) indicates that shutdown requests should cause only the output of the UPS to turn off.  Setting this object to system(2)
                 indicates that shutdown requests will cause the entire UPS system to turn off"
    ::= { upsControl 1 }

upsShutdownAfterDelay OBJECT-TYPE
    SYNTAX      INTEGER
    MAX-ACCESS  read-write
    STATUS      current
    DESCRIPTION "Setting this object will shutdown (i.e., turn off) either the UPS output or the UPS system (as determined by the value of upsShutdownType at the time of
                shutdown) after the indicated number of seconds, or less if the UPS batteries become depleted. Setting this object to 0 will cause the shutdown to occur
                immediately.  Setting this object to -1 will abort the countdown.  If the system is already in the desired state at the time the countdown reaches 0, then
                nothing will happen.  That is, there is no additional action at that time if upsShutdownType = system and the system is already off.  Similarly, there is no
                additional action at that time if upsShutdownType = output and the output is already off.  When read, upsShutdownAfterDelay will return the number of
                seconds remaining until shutdown, or -1 if no shutdown countdown is in effect.  On some systems, if the agent is restarted while a shutdown countdown is in effect,
                the countdown may be aborted.  Sets to this object override any upsShutdownAfterDelay already in effect"
    ::= { upsControl 2 }

upsStartupAfterDelay OBJECT-TYPE
    SYNTAX      INTEGER
    MAX-ACCESS  read-write
    STATUS      current
    DESCRIPTION "Setting this object will start the output after the indicated number of seconds, including starting the UPS, if necessary.  Setting this object to 0 will
                cause the startup to occur immediately.  Setting this object to -1 will abort the countdown.  If the output is already on at the time the countdown reaches 0,
                then nothing will happen.  Sets to this object override the effect of any upsStartupAfterDelay countdown or upsRebootWithDuration countdown in progress.
                When read, upsStartupAfterDelay will return the number of seconds until startup, or -1 if no startup countdown is in effect.  If the countdown expires during
                a utility failure, the startup shall not occur until the utility power is restored.  On some systems, if the agent is restarted while a startup countdown
                is in effect, the countdown is aborted"
    ::= { upsControl 3 }

upsRebootWithDuration OBJECT-TYPE
    SYNTAX      INTEGER
    MAX-ACCESS  read-write
    STATUS      current
    DESCRIPTION "Setting this object will immediately shutdown (i.e., turn off) either the UPS output or the UPS system (as determined by the value of upsShutdownType at the time
                of shutdown) for a period equal to the indicated number of seconds, after which time the output will be started, including starting the UPS, if necessary.  If
                the number of seconds required to perform the request is greater than the requested duration, then the requested shutdown and startup cycle shall be performed in
                the minimum time possible, but in no case shall this require more than the requested duration plus 60 seconds.  When read, upsRebootWithDuration shall return the
                number of seconds remaining in the countdown, or -1 if no countdown is in progress.  If the startup should occur during a utility failure, the startup shall not
                occur until the utility power is restored"
    ::= { upsControl 4 }

upsAutoRestart OBJECT-TYPE
    SYNTAX      INTEGER { on(1), off(2) }
    MAX-ACCESS  read-write
    STATUS      current
    DESCRIPTION "Setting this object to 'on' will cause the UPS system to restart after a shutdown if the shutdown occurred during a power loss as a result of either a
                upsShutdownAfterDelay or an internal battery depleted condition.  Setting this object to 'off' will prevent the UPS system from restarting after a shutdown until
                an operator manually or remotely explicitly restarts it.  If the UPS is in a startup or reboot countdown, then the UPS will not restart until that delay has been satisfied"
    ::= { upsControl 5 }

-- The Configuration group.

upsConfigInputVoltage OBJECT-TYPE
    SYNTAX      INTEGER
    MAX-ACCESS  read-write
    STATUS      current
    DESCRIPTION "The magnitude of the nominal input voltage.  On those systems which support read-write access to this object, if there is an attempt to set this variable to
                 a value that is not supported, the request must be rejected and the agent shall respond with an appropriate error message, i.e., badValue for SNMPv1, or inconsistentValue for SNMPv2"
    ::= { upsConfig 1 }

upsConfigInputFreq OBJECT-TYPE
    SYNTAX      INTEGER
    MAX-ACCESS  read-write
    STATUS      current
    DESCRIPTION "The nominal input frequency.  On those systems which support read-write access to this object, if there is an attempt to set this variable to a value that is not
                supported, the request must be rejected and the agent shall respond with an appropriate error message, i.e., badValue for SNMPv1, or inconsistentValue for SNMPv2"
    ::= { upsConfig 2 }

upsConfigOutputVoltage OBJECT-TYPE
    SYNTAX      INTEGER
    MAX-ACCESS  read-write
    STATUS      current
    DESCRIPTION "The magnitude of the nominal output voltage.  On those systems which support read-write access to this object, if there is an attempt to set this variable to
                a value that is not supported, the request must be rejected and the agent shall respond with an appropriate error message, i.e., badValue for SNMPv1, or inconsistentValue for SNMPv2"
    ::= { upsConfig 3 }

upsConfigOutputFreq OBJECT-TYPE
    SYNTAX      INTEGER
    MAX-ACCESS  read-write
    STATUS      current
    DESCRIPTION "The nominal output frequency.  On those systems which support read-write access to this object, if there is an attempt to set this variable to a value that is not
                supported, the request must be rejected and the agent shall respond with an appropriate error message, i.e., badValue for SNMPv1, or inconsistentValue for SNMPv2"
    ::= { upsConfig 4 }

upsConfigOutputVA OBJECT-TYPE
    SYNTAX      INTEGER
    MAX-ACCESS  read-only
    STATUS      current
    DESCRIPTION "The magnitude of the nominal Volt-Amp rating"
    ::= { upsConfig 5 }

upsConfigOutputPower OBJECT-TYPE
    SYNTAX      INTEGER
    MAX-ACCESS  read-only
    STATUS      current
    DESCRIPTION "The magnitude of the nominal true power rating"
    ::= { upsConfig 6 }

upsConfigLowBattTime OBJECT-TYPE
    SYNTAX      INTEGER
    MAX-ACCESS  read-write
    STATUS      current
    DESCRIPTION "The value of upsEstimatedMinutesRemaining at which a lowBattery condition is declared.  For agents which support only discrete (discontinuous) values, then the
                agent shall round up to the next supported value.  If the requested value is larger than the largest supported value, then the largest supported value shall be selected"
    ::= { upsConfig 7 }

upsConfigAudibleStatus OBJECT-TYPE
    SYNTAX      INTEGER { disabled(1), enabled(2), muted(3) }
    MAX-ACCESS  read-write
    STATUS      current
    DESCRIPTION "The requested state of the audible alarm.  When in the disabled state, the audible alarm should never sound.  The enabled state is self-describing.
                Setting this object to muted(3) when the audible alarm is sounding shall temporarily silence the alarm.  It will remain muted until it would normally stop sounding and
                the value returned for read operations during this period shall equal muted(3).  At the end of this period, the value shall revert to enabled(2).  Writes of the value muted(3)
                when the audible alarm is not sounding shall be accepted but otherwise shall have no effect"
    ::= { upsConfig 8 }

upsConfigLowVoltageTransferPoint OBJECT-TYPE
    SYNTAX      INTEGER
    MAX-ACCESS  read-write
    STATUS      current
    DESCRIPTION "The minimum input line voltage allowed before the UPS system transfers to battery backup"
    ::= { upsConfig 9 }

upsConfigHighVoltageTransferPoint OBJECT-TYPE
    SYNTAX      INTEGER
    MAX-ACCESS  read-write
    STATUS      current
    DESCRIPTION "The maximum line voltage allowed before the UPS system transfers to battery backup"
    ::= { upsConfig 10 }

------------------------------
-- Device
------------------------------

name OBJECT-TYPE
    SYNTAX      DisplayString (SIZE (0..16))
    MAX-ACCESS  read-only
    STATUS      current
    DESCRIPTION "Name of the controller"
    ::= { params 1 }

version OBJECT-TYPE
    SYNTAX      DisplayString (SIZE (0..16))
    MAX-ACCESS  read-only
    STATUS      current
    DESCRIPTION "Version firmware"
    ::= { params 2 }

sn OBJECT-TYPE
    SYNTAX      INTEGER
    MAX-ACCESS  read-only
    STATUS      current
    DESCRIPTION "Serial number"
    ::= { params 3 }

mac OBJECT-TYPE
    SYNTAX DisplayString (SIZE (0..16))
    MAX-ACCESS  read-only
    STATUS      current
    DESCRIPTION "MAC address"
    ::= { params 4 }

tempIn OBJECT-TYPE
    SYNTAX      INTEGER
    MAX-ACCESS  read-only
    STATUS      current
    DESCRIPTION "Temperature inside (C)"
    ::= { params 5 }

tempOut OBJECT-TYPE
    SYNTAX      INTEGER
    MAX-ACCESS  read-only
    STATUS      current
    DESCRIPTION "Temperature outside (C)"
    ::= { params 6 }

out1 OBJECT-TYPE
    SYNTAX      INTEGER { normal(0), alarm(1) }
    MAX-ACCESS  read-only
    STATUS      current
    DESCRIPTION "State of OUT1"
    ::= { params 7 }

out2 OBJECT-TYPE
    SYNTAX      INTEGER { normal(0), alarm(1) }
    MAX-ACCESS  read-only
    STATUS      current
    DESCRIPTION "State of OUT2"
    ::= { params 8 }

out3 OBJECT-TYPE
    SYNTAX      INTEGER { normal(0), alarm(1) }
    MAX-ACCESS  read-only
    STATUS      current
    DESCRIPTION "State of OUT3"
    ::= { params 9 }

fire OBJECT-TYPE
    SYNTAX      INTEGER { normal(0), alarm(1) }
    MAX-ACCESS  read-only
    STATUS      current
    DESCRIPTION "State of fire sensor"
    ::= { params 10 }

serverIP OBJECT-TYPE
    SYNTAX IpAddress
    MAX-ACCESS  read-write
    STATUS      current
    DESCRIPTION "Server IP-address"
    ::= { params 11 }

location OBJECT-TYPE
    SYNTAX DisplayString (SIZE (0..24))
    MAX-ACCESS  read-write
    STATUS      current
    DESCRIPTION "location of the controller"
    ::= { params 12 }

systemUpTime OBJECT-TYPE
    SYNTAX TimeTicks
    MAX-ACCESS read-only
    STATUS     current
    DESCRIPTION "System up time"
    ::= { params 13 }

upsLink OBJECT-TYPE
    SYNTAX      INTEGER { no-connection(0), connected(1) }
    MAX-ACCESS  read-only
    STATUS      current
    DESCRIPTION "State of UPS link"
    ::= { params 14 }

upsState OBJECT-TYPE
    SYNTAX      INTEGER { normal(0), alarm(1) }
    MAX-ACCESS  read-only
    STATUS      current
    DESCRIPTION "State of UPS"
    ::= { params 15 }

upsBatState OBJECT-TYPE
    SYNTAX      INTEGER { normal(0), alarm(1), unknown(2) }
    MAX-ACCESS  read-only
    STATUS      current
    DESCRIPTION "State of UPS battery"
    ::= { params 16 }

upsBeep OBJECT-TYPE
    SYNTAX      INTEGER { off(0), on(1) }
    MAX-ACCESS  read-only
    STATUS      current
    DESCRIPTION "State of beep UPS"
    ::= { params 17 }

upsMode OBJECT-TYPE
    SYNTAX      INTEGER { powerline(0), battery(1), unknown(2) }
    MAX-ACCESS  read-only
    STATUS      current
    DESCRIPTION "Mode of UPS"
    ::= { params 18 }

upsInVol OBJECT-TYPE
    SYNTAX      INTEGER
    MAX-ACCESS  read-only
    STATUS      current
    DESCRIPTION "Input voltage UPS (0.1V)"
    ::= { params 19 }

upsFreq OBJECT-TYPE
    SYNTAX      INTEGER
    MAX-ACCESS  read-only
    STATUS      current
    DESCRIPTION "Frequency UPS (0.1 Hz)"
    ::= { params 20 }

upsOutVol OBJECT-TYPE
    SYNTAX      INTEGER
    MAX-ACCESS  read-only
    STATUS      current
    DESCRIPTION "Output voltage UPS (0.1V)"
    ::= { params 21 }

upsLoadP OBJECT-TYPE
    SYNTAX      INTEGER
    MAX-ACCESS  read-only
    STATUS      current
    DESCRIPTION "Output load UPS (%)"
    ::= { params 22 }

upsLoadW OBJECT-TYPE
    SYNTAX      INTEGER
    MAX-ACCESS  read-only
    STATUS      current
    DESCRIPTION "Output load UPS (W)"
    ::= { params 23 }

upsBatVol OBJECT-TYPE
    SYNTAX      INTEGER
    MAX-ACCESS  read-only
    STATUS      current
    DESCRIPTION "Battery voltage UPS (0.1V)"
    ::= { params 24 }

upsBatCap OBJECT-TYPE
    SYNTAX      INTEGER
    MAX-ACCESS  read-only
    STATUS      current
    DESCRIPTION "Battery capacity UPS (%)"
    ::= { params 25 }

upsReset OBJECT-TYPE
    SYNTAX INTEGER
    MAX-ACCESS  read-write
    STATUS      current
    DESCRIPTION "Reset of UPS (Any value resets the UPS)"
    ::= { params 26 }

deviceReset OBJECT-TYPE
    SYNTAX INTEGER
    MAX-ACCESS  read-write
    STATUS      current
    DESCRIPTION "Reset of device (Any value resets the device)"
    ::= { params 27 }

upsWorkBatTime OBJECT-TYPE
    SYNTAX      INTEGER
    MAX-ACCESS  read-only
    STATUS      current
    DESCRIPTION "Duration of the last shutdown UPS (sec)"
    ::= { params 28 }

upsNomPower OBJECT-TYPE
    SYNTAX      INTEGER
    MAX-ACCESS  read-only
    STATUS      current
    DESCRIPTION "Rated power of UPS (W)"
    ::= { params 29 }

upsCompany OBJECT-TYPE
    SYNTAX      DisplayString (SIZE (0..15))
    MAX-ACCESS  read-only
    STATUS      current
    DESCRIPTION "Manufacturer of UPS"
    ::= { params 30 }

upsModel OBJECT-TYPE
    SYNTAX      DisplayString (SIZE (0..10))
    MAX-ACCESS  read-only
    STATUS      current
    DESCRIPTION "Model of UPS"
    ::= { params 31 }

upsSW OBJECT-TYPE
    SYNTAX      DisplayString (SIZE (0..10))
    MAX-ACCESS  read-only
    STATUS      current
    DESCRIPTION "Version of UPS"
    ::= { params 32 }

upsRemainingBatTime OBJECT-TYPE
    SYNTAX      INTEGER
    MAX-ACCESS  read-only
    STATUS      current
    DESCRIPTION "Remaining battery time UPS (min)"
    ::= { params 33 }

unixTime OBJECT-TYPE
    SYNTAX      Counter
    MAX-ACCESS  read-write
    STATUS      current
    DESCRIPTION "The Unix system time. Measured in seconds since January 1, 1970 GMT"
    ::= { params 34 }

------------------------------

alUPSMode NOTIFICATION-TYPE
    OBJECTS     { upsMode }
    STATUS      current
    DESCRIPTION "Alarm mode of UPS"
    ::= { traps 1 }

alInVol NOTIFICATION-TYPE
    OBJECTS     { upsInVol }
    STATUS      current
    DESCRIPTION "Alarm input voltage"
    ::= { traps 2 }

alOutVol NOTIFICATION-TYPE
    OBJECTS     { upsOutVol }
    STATUS      current
    DESCRIPTION "Alarm output voltage"
    ::= { traps 3 }

alUPSBatCap NOTIFICATION-TYPE
    OBJECTS     { upsBatCap }
    STATUS      current
    DESCRIPTION "Alarm UPS battery capacity"
    ::= { traps 4 }

alUPSBatVol NOTIFICATION-TYPE
    OBJECTS     { upsBatVol }
    STATUS      current
    DESCRIPTION "Alarm UPS battery voltage"
    ::= { traps 5 }

alUPSLoadP NOTIFICATION-TYPE
    OBJECTS     { upsLoadP }
    STATUS      current
    DESCRIPTION "Alarm UPS output load (%)"
    ::= { traps 6 }

alTempIn NOTIFICATION-TYPE
    OBJECTS     { tempIn }
    STATUS      current
    DESCRIPTION "Alarm temperature inside"
    ::= { traps 7 }

alTempOut NOTIFICATION-TYPE
    OBJECTS     { tempOut }
    STATUS      current
    DESCRIPTION "Alarm temperature outside"
    ::= { traps 8 }

alFire NOTIFICATION-TYPE
    OBJECTS     { dire }
    STATUS      current
    DESCRIPTION "Alarm fire sensor"
    ::= { traps 9 }

END
